module srl_nokia-tools-clock {
  yang-version 1.1;
  namespace "urn:srl_nokia/tools-clock";
  prefix srl-tools-info;

  import srl_nokia-tools-system {
    prefix srl-tools-system;
  }
  import srl_nokia-extensions {
    prefix srl-ext;
  }

  description
    "This module defines operational commands related to the system clock.";

  revision 2020-06-30 {
    description
      "SRLinux 20.6.1";
  }

  grouping tools-clock-top {
    container clock {
      description
        "Top-level container for operational commands related to the system clock";
      leaf set-time {
        description
          "Sets the current system time to the specified value";
        type string {
          pattern '(\d{4}-\d{2}-\d{2} \d{2}:\d{2}:\d{2}|\d{2}:\d{2}:\d{2})' {
            error-message "Date/time must be in the format YYYY-MM-DD HH:MM:SS, HH:MM:SS";
          }
        }
      }
    }
  }

  augment "/srl-tools-system:system" {
    srl-ext:first-released "20.6.1";
    uses tools-clock-top;
  }
}
