module srl_nokia-load-balancing {
  yang-version 1.1;
  namespace "urn:srl_nokia/load-balancing";
  prefix srl_nokia-lb;

  import srl_nokia-system { prefix srl-system; }
  import srl_nokia-features { prefix srl-feat; }

  description
    "This module defines configuration and operational state data related to ECMP and other load-balancing options.";

  revision 2021-03-31 {
    description
      "SRLinux 21.3.1";
  }
  revision 2020-06-30 {
    description
      "SRLinux 20.6.1";
  }
  revision 2019-11-30 {
    description
      "SRLinux 19.11.1";
  }

  grouping ip-load-balancing-top {
    container ip-load-balancing {
      presence "Adjust system-wide IP ECMP load balancing options.";
      container hash-keys {
        description
          "Container for hash-keys that will be used to load-balance IP traffic across IP next-hops that form an ECMP set";
        leaf destination-address {
          description
            "Include the destination IP address in the hash calculation";
          type boolean;
          default true;
        }
        leaf destination-port {
          description
            "Include the destination TCP/UDP port number in the hash calculation if the packet is an unfragmented IP packet carrying a TCP/UDP payload";
          type boolean;
          default true;
        }
        leaf hash-seed {
          type uint16;
          default 0;
          description
            "A configured hash seed to override the default value of 0

            When different routers have a different hash-seed traffic polarization effects can be minimized.";
        }
        leaf ipv6-flow-label {
          description
            "Include the IPv6 flow label in the hash calculation if the packet is an IPv6 packet
            
            It is expected that the IPv6 flow label value is written by the server or other host originating the flow and not changed by any intermediate switch or router.";
          type boolean;
          default false;
        }
        leaf protocol {
          description
            "Include the IP protocol number in the hash calculation. For an IPv6 packet this is protocol value in the next-header field of the last extension header.";
          type boolean;
          default true;
        }
        leaf source-address {
          description
            "Include the source IP address in the hash calculation";
          type boolean;
          default true;
        }
        leaf source-port {
          description
            "Include the source TCP/UDP port number in the hash calculation if the packet is an unfragmented IP packet carrying a TCP/UDP payload";
          type boolean;
          default true;
        }
        leaf vlan {
          if-feature "srl-feat:trident3 or srl-feat:tomahawk3";
          description
            "Include the received VLAN ID in the hash calculation";
          type boolean;
        }
      }
    }
  }

  augment "/srl-system:system" {
    uses ip-load-balancing-top;
  }
}
