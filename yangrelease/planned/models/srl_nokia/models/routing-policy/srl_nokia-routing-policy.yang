module srl_nokia-routing-policy {

  yang-version 1.1;

  namespace "urn:srl_nokia/routing-policy";

  prefix "srl_rpol";

  import srl_nokia-common { prefix srl_nokia-comm; }
  import srl_nokia-extensions { prefix srl_nokia-ext; }
  import srl_nokia-policy-types { prefix srl_nokia-pol-types; }
  import srl_nokia-ospf-types { prefix srl_nokia-ospf-types; }

  description
    "YANG model for route policies. It supports widely used constructs for managing how routes are imported, exported, and modified across different routing protocols.";

  revision 2021-03-31 {
    description
      "SRLinux 21.3.1";
  }
  revision 2020-06-30 {
    description
      "SRLinux 20.6.1";
  }
  revision 2019-11-30 {
    description
      "SRLinux 19.11.1";
  }

  grouping prefix-top {
    list prefix {
      key "ip-prefix mask-length-range";
      description
        "List of prefixes in the prefix set";
      leaf ip-prefix {
        type srl_nokia-comm:ip-prefix;
        description
          "The IPv4 or IPv6 prefix in CIDR notation";
      }
      leaf mask-length-range {
        type string {
          pattern '([0-9]+\.\.[0-9]+)|exact';
        }
        description
          "The range of prefix lengths to match

          Example: 10.3.192.0/21 through 10.3.192.0/24 would be expressed as prefix: 10.3.192.0/21, mask-length-range: 21..24.

          Example: 10.3.192.0/21 would be expressed as prefix: 10.3.192.0/21,
          mask-length-range: exact";
      }
    }
  }

  grouping as-path-set-top {
    list as-path-set {
      srl_nokia-ext:first-released "19.11.1";
      key "name";
      description "AS Path regular expressions for use in policy entries";
      leaf name {
        type srl_nokia-comm:name;
        description
          "A name used to identify the AS path regular expression";
      }
      leaf expression {
        type srl_nokia-pol-types:as-path-regexp;
        description
          "A regular expression where each AS number is an elemental term";
      }
    }
  }

  grouping prefix-set-top {
    list prefix-set {
      srl_nokia-ext:first-released "19.11.1";
      key "name";
      description
        "List of defined prefix sets";

      leaf name {
        type srl_nokia-comm:name;
        description
          "A name used to identify the prefix set";
      }
      uses prefix-top;
    }
  }

  grouping esi-set {
    list esi-set {
      srl_nokia-ext:first-released "20.12.1";
      if-feature "srl_nokia-feat:evpn";
      key "name";
      description
        "List of Ethernet Segment Identifier (ESI) sets used for matching EVPN routes";

      leaf name {
        type srl_nokia-comm:name;
        description
          "A name used to identify the ESI set";
      }
      list esi {
        description
          "List of Ethernet Segment Identifier values that form a set";
        key id;
        leaf id {
          type srl_nokia-comm:esi;
          description
            "An Ethernet Segment Identifier";
        }
      }
    }
  }

  grouping ethernet-tag-set {
    list ethernet-tag-set {
      srl_nokia-ext:first-released "20.12.1";
      if-feature "srl_nokia-feat:evpn";
      key "name";
      description
        "List of Ethernet Tag ID sets used for matching EVPN routes";

      leaf name {
        type srl_nokia-comm:name;
        description
          "A name used to identify the Ethernet Tag ID set";
      }
      list ethernet-tag-id {
        description
          "List of Ethernet Tag ID values that form a set";
        key id;
        leaf id {
          type uint32;
          description
            "An Ethernet Tag ID";
        }
      }
    }
  }

  grouping mac-set {
    list mac-set {
      srl_nokia-ext:first-released "20.12.1";
      if-feature "srl_nokia-feat:evpn";
      key "name";
      description
        "List of MAC address sets used for matching EVPN routes";

      leaf name {
        type srl_nokia-comm:name;
        description
          "A name used to identify the MAC address set";
      }
      list mac-address {
        description
          "List of MAC addresses that form a set";
        key address;
        leaf address {
          type srl_nokia-comm:mac-address;
          description
            "A MAC address";
        }
      }
    }
  }

  grouping community-member-top {
    description
      "Members of a community set";

    leaf-list member {
      srl_nokia-ext:no-globbing;
      min-elements 1;
      type union {
        type srl_nokia-pol-types:bgp-std-community-type;
        type srl_nokia-pol-types:bgp-std-community-regexp-type;
        type srl_nokia-pol-types:bgp-std-community-well-known-type;
        type srl_nokia-pol-types:bgp-large-community-type;
        type srl_nokia-pol-types:bgp-large-community-regexp-type;
      }
      description
        "A standard BGP community value, regular expression or well-known name or else a large BGP community value or regular expression.
        
        The maximum length is 110 characters.";
    }
  }

  grouping community-set-top {
    list community-set {
      srl_nokia-ext:first-released "19.11.1";
      key "name";
      description
          "List of BGP community sets containing standard and large BGP communities";
      leaf name {
        type srl_nokia-comm:name;
        description
          "A name used to identify the community set";
      }
      uses community-member-top;
    }
  }

  grouping tag-member-top {
    description
      "Members of a tag set";

    leaf-list tag-value {
      ordered-by user;
      type union {
        type srl_nokia-pol-types:igp-32bit-admin-tag-type;
        type srl_nokia-pol-types:igp-64bit-admin-tag-type;
      }
      description
        "List of 32-bit and/or 64-bit administrative tag values.";
    }
  }

    grouping tag-set-top {
    list tag-set {
      srl_nokia-ext:first-released "20.12.1";
      key "name";
      description
          "List of administrative tag sets";
      leaf name {
        type srl_nokia-comm:name;
        description
          "A name used to identify the tag set";
      }
      uses tag-member-top;
    }
  }

  grouping common-action-top {
    description "Common grouping containing policy actions";

    container bgp {
      srl_nokia-ext:first-released "19.11.1";
      container as-path {
        description "Modify AS Path attribute of routes";
        leaf remove {
          srl_nokia-ext:first-released "20.6.1";
          description
            "Clear the AS path to make it empty.";
          type boolean;
        }
        leaf-list replace {
          srl_nokia-ext:first-released "20.6.1";
          type srl_nokia-pol-types:as-number;
          ordered-by user;
          must "not(../remove)";
          description
            "Clear the existing AS path and replace it a new AS_SEQUENCE containing the listed AS numbers.
            
            This takes precedence over a prepend action; the prepend action is not performed if a remove or replace action is specified.";
        }
        container prepend {
          description
            "Prepend a BGP AS number to the AS Path attribute of routes";
          leaf as-number {
            type union {
              type srl_nokia-pol-types:as-number;
              type enumeration {
                enum "auto" {value 1;}
              }
            }
            description
              "The AS number to prepend to the AS Path attributes

              If 'auto' is specified then the peer's AS number is used in the context of an import policy and the local AS number is used in the context of an export policy.";
          }
          leaf repeat-n {
            type uint8 {
              range "1..50";
            }
            default "1";
            description
              "The number of repetitions of the prepended AS number";
          }
        } // container prepend
      } // container as-path

      container communities {
        description "Modify BGP communities attached to routes";
        leaf add {
          type leafref {
            path "/srl_rpol:routing-policy/srl_rpol:community-set/name";
          }
          description
            "Reference to a community-set name

            All of the non-regex community members in the referenced community-set are added to the COMMUNTIES and LARGE_COMMUNITIES attributes.";
        }
        leaf remove {
          type leafref {
            path "/srl_rpol:routing-policy/srl_rpol:community-set/name";
          }
          description
            "Reference to a community-set name

            The communities in the route are compared to all of the community members in the referenced community-set, and all matching communities are removed from the COMMUNITIES and LARGE_COMMUNITIES  attributes.";
        }
        leaf replace {
          type leafref {
            path "/srl_rpol:routing-policy/srl_rpol:community-set/name";
          }
          description
            "Reference to a community-set name

            All of the existing communities are deleted and then all of the non-regex community members in the referenced community-set are encoded in new COMMUNTIES and LARGE_COMMUNITIES attributes.";
          must "not(../remove or ../add)";
        }
      }
      container local-preference {
        leaf set {
          type uint32;
          description
            "The new value of LOCAL_PREF to write into the matching BGP routes";
        }
      }
      /*
      container next-hop {
        description
          "Container for BGP next-hop modifications";
        srl_nokia-ext:first-released "20.12.1";
        leaf self {
          description
            "Apply next-hop-self to BGP routes.
            
            When set to true, the next-hop in all matching BGP routes advertised to the peer is set equal to the local-address used on this session (or to the router ID if the NLRI is IPv6 and there is no IPv6 local address to use). This is independent of the route origin (EBGP, IBGP or redistributed direct/static/aggregate route). When set to false, normal BGP rules from RFC 4271 apply.";
          type boolean;
        }
        leaf unchanged {
          description
            "Apply next-hop unchanged to BGP routes.
            
            When set to true, the next-hop in all matching BGP routes re-advertised to the peer is set equal to the RIB-IN value.";
          type boolean;
        }
      }
      */
      container origin {
        leaf set {
          type enumeration {
            enum "igp";
            enum "egp";
            enum "incomplete";
          }
          description
            "The new value of the ORIGIN attribute to write into the matching BGP routes";
        }
      }
    }
    container route-tags {
      srl_nokia-ext:first-released "20.12.1";
      description "Container for route tag modifications";
        leaf add {
          type leafref {
            path "/srl_rpol:routing-policy/srl_rpol:tag-set/name";
          }
          description
            "Reference to a tag-set name

            All of the admin tags in the referenced tag-set are added to the accepted IS-IS routes. The first 32-bit admin-tag in the referenced tag-set is encoded in the External Route Tag field of accepted OSPF type 5/7 routes.";
        }
        leaf remove {
          type leafref {
            path "/srl_rpol:routing-policy/srl_rpol:tag-set/name";
          }
          description
            "Reference to a tag-set name

            The admin tag(s) in the IGP route are compared to all of the tag values in the referenced tag-set, and all matching admin tags are removed.";
        }
        leaf replace {
          type leafref {
            path "/srl_rpol:routing-policy/srl_rpol:tag-set/name";
          }
          description
            "Reference to a tag-set name

            All of the existing admin tags are deleted and then all of the admin tags in the referenced tag-set are added to the accepted IS-IS routes and the first 32-bit admin-tag in the referenced tag-set is encoded in the External Route Tag field of accepted OSPF type 5/7 routes.";
          must "not(../remove or ../add)";
        }
    }
  }

  grouping default-action-top {
    srl_nokia-ext:first-released "19.11.1";
    container default-action {
      description "Actions for routes that do not match any policy entry";
      container reject {
        presence "Reject routes that do not match any policy entry";
        description "Reject action";
      }
      container accept {
        presence "Accept routes that do not match any policy entry";
        description "Accept action";
        uses common-action-top;
      }
    } // container default-action
  } // grouping default-action-top

  grouping match-prefix-set {
    description
      "Configuration for prefix-set match criteria";
    leaf prefix-set {
      type leafref {
        path "/srl_rpol:routing-policy/srl_rpol:prefix-set/name";
      }
    description "Reference to a prefix set name";
    }
  }

  grouping match-bgp-evpn {
    container evpn {
      if-feature "srl_nokia-feat:evpn";
      srl_nokia-ext:first-released "20.12.1";
      description
        "Container for match conditions that are specific to BGP EVPN routes.";
      leaf esi-set {
        type leafref {
          path "/srl_rpol:routing-policy/srl_rpol:esi-set/name";
        }
        description
          "An EVPN route (type 1, 2, 4 or 5) meets this confition if it has an Ethernet Segment Identifier that matches a member of the specified esi-set.";
      }
      leaf ethernet-tag-set {
        type leafref {
          path "/srl_rpol:routing-policy/srl_rpol:ethernet-tag-set/name";
        }
        description
          "An EVPN route (type 1, 2, 3 or 5) meets this condition if it has an Ethernet Tag ID that matches a member of the specified ethernet-tag-set.";
      }
      leaf gateway {
        type srl_nokia-comm:ip-address;
        description
          "An EVPN type-5 route meets this condition if its gateway IP address matches the specified IPv4 or IPv6 address.";
      }
      leaf mac-set {
        type leafref {
          path "/srl_rpol:routing-policy/srl_rpol:mac-set/name";
        }
        description
          "An EVPN type-2 route meets this condition if it has a MAC address that matches a member of the specified mac-set.";
      }
      leaf originator-ip {
        type srl_nokia-comm:ip-address;
        description
          "An EVPN type 3 or type 4 route meets this condition if the originating router’s IP address in the route matches the specified IP address.";
      }
      leaf-list route-type {
        max-elements 1;
        type srl_nokia-pol-types:evpn-type;
        description
          "An EVPN route meets this condition if the route-type field in the NLRI matches the specified value.";
      }
    }
  }

  grouping match-bgp {
    container bgp {
      description
        "Configuration for BGP-specific policy match criteria";
      leaf as-path-set {
        description
          "Reference to an as-path-set name

          A route meets this condition if it matches the regular expression";
        type leafref {
          path "/srl_rpol:routing-policy/srl_rpol:as-path-set/name";
        }
      }
      container as-path-length {
        description
          "A BGP route matches this condition if the number of (unique) AS numbers in its AS_PATH matches this value or the range implied by the value+operator.";
        leaf value {
          type uint8 {
            range "0..255";
          }
          description
            "The number of (unique) AS numbers in the AS path";
        }
        leaf operator {
          type srl_nokia-pol-types:comparison-operator-type;
          default 'eq';
          description
            "The comparison operator that applies to the value";
        }
        leaf unique {
          type boolean;
          default false;
          description
            "Count a repeated sequence of the same AS number as just 1 element";
        }
      }
      leaf community-set {
        description
          "Reference to a community-set name

          A route meets this condition if has any community value matching a community member in the referenced community-set";
        type leafref {
          path "/srl_rpol:routing-policy/srl_rpol:community-set/name";
        }
      }
      leaf route-distinguisher {
        description
          "Match BGP VPN routes based on the route-distinguisher value in the NLRI. (Initially this will only match EVPN routes.)";
        type srl_nokia-comm:route-distinguisher;
      }
      uses match-bgp-evpn;
    }
  }
  grouping match-general {
    description "Configuration for general match criteria applicable to multiple route types";
    leaf family {
      type srl_nokia-pol-types:bgp-family-type;
      description
        "The name of an address family

        A route meets this condition if the prefix belongs to the indicated address family.";
    }
    leaf protocol {
      type identityref {
        base srl_nokia-comm:ip-route-owner;
      }
      description "The protocol name or route owner name to match";
    }
    leaf tag-set {
      srl_nokia-ext:first-released "20.12.1";
      description
        "Reference to an admin-tag set name

        A route meets this condition if it has an admin tag that is included in the referenced tag-set";
      type leafref {
        path "/srl_rpol:routing-policy/srl_rpol:tag-set/name";
      }
    }
  }

  grouping match-igp {
    container isis {
      srl_nokia-ext:first-released "20.12.1";
      description
        "Configuration for ISIS-specific policy match criteria";
      leaf level {
        description "IS-IS route level";
        type uint8 {
          range "1..2";
        }
      }
      leaf route-type {
        description
          "An IS-IS IPv4 prefix is external if it is signalled in TLV 130 or TLV135 with RFC 7794 X flag=1. An IS-IS IPv6 prefix is external if the TLV 236/TLV 237 external bit = 1.";
        type enumeration {
          enum "internal";
          enum "external";
        }
      }
    }
    container ospf {
      srl_nokia-ext:first-released "20.12.1";
      description
        "Configuration for OSPF-specific policy match criteria";
      leaf area-id {
        type srl_nokia-ospf-types:ospf-area-identifier;
        description
          "The area identifier as a dotted-quad.";
      }
      leaf route-type {
        description
          "The OSPF route type.";
        type identityref {
          base srl_nokia-ospf-types:ospf-path-type;
        }
      }
      leaf instance-id {
        description
          "OSPFv3 instance identifier";
        type uint32 {
          range "0..255";
        }
      }
    }
  }

  grouping match-top {
    description
      "Top-level grouping for match criteria";

    container match {
      srl_nokia-ext:first-released "19.11.1";
      description
        "Match conditions of the policy statement";

      uses match-prefix-set;
      uses match-general;
      uses match-bgp;
      uses match-igp;
    }
  }

  grouping action-top {
    description
       "Top-level grouping for policy actions";

    container action {
      srl_nokia-ext:first-released "19.11.1";
      description "Actions for routes that match the policy statement";
      container reject {
        presence "Reject routes that match the policy statement";
        description
          "Reject routes that match the policy statement";
      }
      container accept {
        presence "Accept routes that match the policy statement";
        description
          "Reject routes that match the policy statement";
        uses common-action-top;
      }
    }
  }

  grouping statement-top {
    description
      "Top-level grouping for the policy statements list";

      list statement {
        srl_nokia-ext:first-released "19.11.1";
        key "sequence-id";
        // requires a unique id for lists
        ordered-by system;
        description
          "Policy statements group conditions and actions within a policy definition.  They are evaluated in the order of their sequence id.";

        leaf sequence-id {
          type uint32;
          description
            "Number indicating when this policy statement should be evaluated relative to other policy statements

            Lower numbered statements are evaluated before higher numbered statements.";
        }

        uses match-top;
        uses action-top;
      }
  }

  grouping policy-top {
    description
      "Top-level grouping for the policy list";

      list policy {
        srl_nokia-ext:first-released "19.11.1";
        key "name";
        description
          "List of policy definitions, keyed by unique name

          These policy definitions are expected to be referenced (by name) in policy in import-policy and/or export-policy statements.";

        leaf name {
            type srl_nokia-comm:name;
          description
            "A name used to identify the policy";
        }
        uses default-action-top;
        uses statement-top;
      }
  }

  grouping routing-policy-top {
    description
      "Top level container for route policies";

    container routing-policy {
      srl_nokia-ext:first-released "19.11.1";
      description
        "Top-level container for all routing policy configuration";

      uses as-path-set-top;
      uses community-set-top;
      uses esi-set;
      uses ethernet-tag-set;
      uses mac-set;
      uses prefix-set-top;
      uses tag-set-top;
      uses policy-top;
    }
  }

  uses routing-policy-top;
}
