module srl_nokia-network-instance-future {

  yang-version 1.1;

  // namespace
  namespace "urn:srl_nokia/network-instance-future";

  prefix "srl_nokia-netinst-future";

  import srl_nokia-common { prefix srl_nokia-comm; }
  import srl_nokia-network-instance { prefix srl_nokia-netinst; }
  import srl_nokia-routing-policy { prefix srl-rpol; }

  description
    "This yang file augments network-instance with features and capabilities planned for phase 2.";

  revision 2019-11-30 {
    description
      "SRLinux 19.11.1";
  }

  typedef network-instance-subintf-ref {
    type string;
    description
      "Reference type to a specific subinterface of the form <interface-name>.<subinterface-index>";
  }

  typedef route-distinguisher {
    type union {
      // type 0: <2-byte administrator>:<4-byte assigned number>
      type string {
        pattern '^(65[0-5][0-3][0-5]|[1-5][1-5][0-9][0-9][0-9]|'
                + '[1-9]?[1-9]?[0-9][0-9]|[1-9]):'
                + '(4[0-2][0-9][0-4][0-9][0-6][0-7][0-2][0-9][0-5]|'
                + '[0-3][0-9]{9}|[1-9][0-9]{1,8}|[1-9])$';
      }
      // type 1: <ip-address>:<2-byte assigned number>
      type string {
        pattern
          '^(([0-9]|[1-9][0-9]|1[0-9][0-9]|2[0-4][0-9]|25[0-5])\.){3}'
          +  '([0-9]|[1-9][0-9]|1[0-9][0-9]|2[0-4][0-9]|25[0-5]):'
          +  '(65[0-5][0-3][0-5]|[1-5][1-5][0-9][0-9][0-9]|'
          +  '[1-9]?[1-9]?[0-9][0-9]|[1-9])$';
      }
      // type 2: <4-byte as-number>:<2-byte assigned number>
      type string {
        pattern
          '^(4[0-2][0-9][0-4][0-9][0-6][0-7][0-2][0-9][0-5]|'
          + '[0-3][0-9]{9}|[1-9][0-9]{1,8}|[1-9]):'
          + '(65[0-5][0-3][0-5]|[1-5]{2}[0-9]{3}|'
          + '[1-9]{0,2}[0-9][0-9]|[1-9])$';
      }
    }
    description "A route distinguisher value";
    reference "RFC4364";
  }

  identity NI_TYPE {
    description
      "Base type for network instance types.";
  }

  identity MAC-VRF {
    base NI_TYPE;
    description
      "A private Layer 2 switch instance.";
  }

  augment "/srl_nokia-netinst:network-instance" {
    container bgp-vpn {
      leaf route-distinguisher {
        type route-distinguisher;
        description
          "The route distinguisher that should be used for the local VRF or VSI instance when it is signalled via BGP.";
      }
      leaf route-target {
        type string;
      }
      leaf import-policy {
        type leafref {
          path "/srl-rpol:routing-policy/srl-rpol:policy/srl-rpol:name";
        }
      }
      leaf export-policy {
        type leafref {
          path "/srl-rpol:routing-policy/srl-rpol:policy/srl-rpol:name";
        }
      }
    }
    container mac-fdb {
      leaf mac-learning {
        type boolean;
        default true;
        description
          "When this leaf is set to true, MAC learning is enabled for the network instance, such that MAC addresses are learned from ingress frames and added to the FDB.";
        }

      leaf mac-aging-time {
        type uint16;
        units seconds;
        description
          "The number of seconds of inactivity after which the entry in the local FDB is timed out.";
      }

      leaf maximum-entries {
        type uint16;
        description
          "The maximum number of MAC address entries that should be accepted into the FDB";
      }

      list static-entry {
        key mac-address;
        leaf mac-address {
          type srl_nokia-comm:mac-address;
          description
            "MAC address for the static MAC table entry.";
        }
        leaf blackhole {
            type boolean;
            default false;
            description
              "Blackhole MAC";
        }
        leaf subinterface {
          type srl_nokia-netinst:network-instance-subintf-ref;
          description
            "Identifier of subinterface.";
        }
      }
    }
  }
}
