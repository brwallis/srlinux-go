module srl_nokia-tools-dhcp-server{
  yang-version 1.1;
  namespace "urn:srl_nokia/tools-system-dhcp-server";
  prefix srl_nokia-tools-dhcp-server;

  import srl_nokia-tools-system {
    prefix srl_nokia_tools-system;
  }
  import srl_nokia-network-instance {
    prefix srl-netinst;
  }

  description
    "Model for dhcp server operational commands";

  revision 2021-03-31 {
    description
      "SRLinux 21.3.1";
  }

  grouping tools-system-dhcp-server-top {
    container dhcp-server {
      list network-instance {
        description
          "List of network instances to run a dhcp server in";
        key "name";
        leaf name {
          type leafref {
            path "/srl-netinst:network-instance/srl-netinst:name";
          }
        }
        container dhcpv4 {
          container statistics {
            leaf clear {
              type empty;
            }
          }
        }
      }
    }
  }

  augment "/srl_nokia_tools-system:system" {
    uses  tools-system-dhcp-server-top;
  }
}
