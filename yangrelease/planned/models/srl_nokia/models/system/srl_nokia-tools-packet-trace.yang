module srl_nokia-tools-packet-trace {
  yang-version 1.1;
  namespace "urn:srl_nokia/tools-packet-trace";
  prefix srl_nokia-tools-packet-trace;

  import srl_nokia-tools-system {
    prefix srl-tools-system;
  }

  description
    "Model for operational commands on logging";

  revision 2021-03-31 {
    description
      "SRLinux 21.3.1";
  }
  revision 2020-06-30 {
    description
      "SRLinux 20.6.1";
  }
  revision 2019-11-30 {
    description
      "SRLinux 19.11.1";
  }

  grouping tools-packet-trace-top {
    description
      " Top-level grouping for packet-trace tools command";
  		
    typedef restricted-file-name-type {
      // Disallows (a) one single period character, (b) a pair of period characters, and (c) anything with slashes
      type string {
        pattern '([^./][^/]*)|(\.[^\./]+)|(\.\.[^/])+';
      }
    }

    container packet-trace {
      description
        "Top-level grouping for packet-trace operational commands";
      container header-file {
      	leaf file {
      	  type restricted-file-name-type;
      	  description
      	    "Name of local header definition file" ;
      	}
      }
      container interface { 
      	leaf name {
      	  type string;
      	  description
      	    "References the configured name of the interface";
      	}
      }
    }
  }

  augment "/srl-tools-system:system" {
    uses tools-packet-trace-top;
    // + packet-trace header-file <file> ingress-port <phy-port-id>
  }
}
