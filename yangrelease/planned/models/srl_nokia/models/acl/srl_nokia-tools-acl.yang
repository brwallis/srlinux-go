module srl_nokia-tools-acl {
    yang-version 1.1;
    namespace "urn:srl_nokia/tools-acl";
    prefix srl_nokia-tools-acl;

    import srl_nokia-common { prefix srl_nokia-comm; }

    description
            "Model for operational commands on network interfaces and subinterfaces.";

  revision 2019-11-30 {
    description
      "SRLinux 19.11.1";
  }

    grouping ip-common-clear-group {
        container statistics {
            leaf clear {
                type empty;
                description
                        "Reset all statistics of all entries of the filter to zero";
            }
        }
        list entry {
            description "List of filter rules.";
            key sequence-id;
            leaf sequence-id {
                type uint32;
                description
                        "A number to indicate the relative evaluation order of the different entries; lower numbered entries are evaluated before higher numbered entries";
            }
            container statistics {
                leaf clear {
                    type empty;
                    description
                            "Reset all aggregate and per-interface statistics associated with this particular entry to zero";
                }
                container per-interface {
                    description
                            "Container for per-subinterface per-entry statistics";
                    list subinterface {
                        key name;
                        description
                                "List of subinterfaces where the ACL is applied to either input or output traffic";
                        leaf name {
                            type srl_nokia-comm:subinterface-all;
                        }
                        leaf clear {
                            type empty;
                            description
                                    "Reset the per-interface statistics associated with this particular entry and this particular subinterface to zero";
                        }
                    }
                }
            }
        }
    }

    grouping cpm-common-clear-group {
        leaf clear {
            type empty;
            description
                    "Reset all statistics of all entries of the filter to zero";
        }
        list entry {
            description "List of filter rules.";
            key sequence-id;
            leaf sequence-id {
                type uint32;
                description
                        "A number to indicate the relative evaluation order of the different entries; lower numbered entries are evaluated before higher numbered entries";
            }
            container statistics {
                leaf clear {
                    type empty;
                    description
                            "Reset all statistics associated with this particular entry to zero";
                }
            }
        }
    }

    grouping policer-common-clear-group {
        container statistics {
            leaf clear {
                type empty;
                description
                        "Reset all statistics associated with this particular policer to zero";
            }
        }
    }

    container acl {
        description
                "Top level enclosing container for ACL operational tools";
        list ipv4-filter {
            description "List of IPv4 filter policies";
            key name;
            leaf name {
                type srl_nokia-comm:name;
                description "Name of the IPv4 filter policy.";
            }

            uses ip-common-clear-group;
        }

        list ipv6-filter {
            description "List of IPv6 filter policies";
            key name;
            leaf name {
                type srl_nokia-comm:name;
                description "Name of the IPv6 filter policy.";
            }

            uses ip-common-clear-group;
        }

        container cpm-filter {
            description "List of CPM filters";

            container ipv4-filter {
                description "List of CPM IPv4 filter rules";
                uses cpm-common-clear-group;
            }

            container ipv6-filter {
                description "List of CPM IPv6 filter rules";
                uses cpm-common-clear-group;
            }
        }

        container policers {
            description
                "List of policers used by ACL entries";

            list system-cpu-policer {
                description "List of system CPU policers";
                key name;
                leaf name {
                    description "Name of the system cpu policer";
                    type srl_nokia-comm:name;
                }

                uses policer-common-clear-group;
            }

            list policer {
                description "List of hardware policers";
                key name;
                leaf name {
                    description "Name of the hardware policer";
                    type srl_nokia-comm:name;
                }

                uses policer-common-clear-group;
            }
        }
    }
}
