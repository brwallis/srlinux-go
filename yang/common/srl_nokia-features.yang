module srl_nokia-features {
  yang-version 1.1;
  namespace "urn:srl_nokia/features";
  prefix srl_nokia-feat;

  description
    "YANG module detailing SRLinux features";

  // features - alphabetical

  revision 2021-03-31 {
    description
      "SRLinux 21.3.1";
  }
  revision 2020-06-30 {
    description
      "SRLinux 20.6.1";
  }

  feature anycast-gw {
    description
      "Support for bridged feature and anycast-gw configuration on interface";
  }

  feature bridged {
    description
      "Support for MAC-VRF services";
  }

  feature chassis {
    description
      "The platform is in a chassis configuration";
  }

  feature evpn {
    description
      "Support for EVPN";
  }

  feature fixed {
    description
      "The platform is in a fixed configuration, i.e. non-chassis platforms";
  }

  feature future-0-0 {
    description
      "Only true in 0.0 stream, false in other streams. The feature is for an unknown future release.";
  }

  feature future-21-6 {
    description
      "Only true in 0.0 stream, false in other streams. The feature is for the 21.6 release. Once the release stream exists this flag will be removed.";
  }

  feature future-21-11 {
    description
      "Only true in 0.0 stream, false in other streams. The feature is for the 21.11 release. Once the release stream exists this flag will be removed.";
  }

  feature isis-mt {
    if-feature future-21-6;
    description
      "Support for isis multi-topology";
  }

  feature lacp-fallback {
    description
      "Support for link aggregation control protocol fallback";
  }

  feature label-management {
    if-feature future-21-6;
    description
      "Support for mpls label management";
  }

  feature lag {
    description
      "Support for link aggregation groups";
  }

  feature ldp {
    if-feature future-21-6;
    description
      "Support for label distribution protocol";
  }

  feature mirroring {
    if-feature future-21-6;
    description
      "Support for mirroring (SPAN/ERSPAN)";
  }

  feature mpls {
    description
      "Support for MPLS";
  }

  feature port-breakout {
    if-feature future-21-6;
    description
      "Support for ethernet port breakout (port connector)";
  }

  feature traffic-engineering {
    if-feature future-21-11;
    description
      "Support for TE DB, BGP-LS and TE advertisement by IGPs";
  }

  feature vrrp {
    if-feature future-0-0;
    description
      "Support for VRRP";
  }

  feature vxlan {
    description
      "Support for VXLAN";
  }

  feature warm-reboot {
    description
      "Support for warm reboot";
  }

  // chipsets - alphabetical

  feature jericho2;

  feature tomahawk3;

  feature trident3;

  feature vxdp;

  // platforms - alphabetical

  feature platform-7220-d1; // 7220 IXR-D1

  feature platform-7220-d2; // 7220 IXR-D2

  feature platform-7220-d3; // 7220 IXR-D3

  feature platform-7220-h2; // 7220 IXR-H2

  feature platform-7220-h3; // 7220 IXT-H3

  feature platform-7250-ixr; // 7250 IXR-6/10

  feature platform-7250-j2;  // J2 pizza

  feature platform-crimson;  // crimson pizza

}
