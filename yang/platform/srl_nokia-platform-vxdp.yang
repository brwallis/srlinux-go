module srl_nokia-platform-vxdp {
  yang-version 1.1;

  // namespace

  namespace "urn:srl_nokia/platform-vxdp";
  prefix srl_nokia-platform-vxdp;

  import srl_nokia-common {
    prefix srl-comm;
  }
  import srl_nokia-features {
    prefix srl-feat;
  }
  import srl_nokia-platform {
    prefix srl-platform;
  }
  import srl_nokia-platform-cpu {
    prefix srl-cpu;
  }

  description
    "This module defines configuration and operational state data related to vXDP";

  revision 2021-11-30 {
    description
      "SRLinux 21.11.1";
  }

  grouping cpu-idle {
    description
      "Definition of idle CPU leaf";
    leaf idle {
      description
        "The aggregate idle percentage of threads";
      type srl-comm:percentage;
    }
  }

  grouping vxdp-config-top {
    description
      "Grouping for vXDP configuration";
    leaf-list cpu-set {
      description
        "The list of CPUs pinned to vXDP threads
        
        These CPUs should be isolated out-of-band of SR Linux";
      type uint8;
    }
  }

  grouping vxdp-state-top {
    description
      "Grouping for vXDP state";
    list cpu {
      config false;
      key id;
      description
        "State information relating to the list of CPUs pinned to vXDP threads";
      leaf id {
        description
          "Reference to a CPU within the configured cpu-set";
        type uint8;
      }
      leaf oper-state {
        description
          "The operational state of the CPU core";
        type srl-comm:oper-state;
      }
      leaf oper-down-reason {
        description
          "The reason (if any) that this CPU is down or degraded";
        type enumeration {
          enum "not-isolated";
          enum "numa-no-memory";
          enum "irq-not-masked";
          enum "sibling-not-isolated";
        }
      }
      leaf socket-id {
        description
          "The socket this CPU resides on";
        type uint8;
      }
      leaf sibling {
        description
          "The sibling CPU (if any) residing on the same core";
        type uint8;
      }
    }
    container statistics {
      config false;
      description
        "Top-level container for statistics relating to vXDP thread utilization";
      container nic {
        description
          "Top-level container for NIC thread statistics";
        uses cpu-idle;
        uses srl-cpu:per-type-statistics;
      }
      container forwarder {
        description
          "Top-level container for forwarder thread statistics";
        uses cpu-idle;
        uses srl-cpu:per-type-statistics;
      }
    }
  }

  grouping vxdp-top {
    description
      "Grouping for vXDP configuration and state";
    container vxdp {
      description
        "Top-level container for vXDP configuration and state";
      if-feature "srl-feat:vxdp";
      uses vxdp-config-top;
      uses vxdp-state-top;
    }
  }

  augment "/srl-platform:platform" {
    uses vxdp-top;
  }
}
