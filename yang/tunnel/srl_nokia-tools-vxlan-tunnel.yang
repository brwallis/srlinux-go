module srl_nokia-tools-vxlan-tunnel {
  yang-version 1.1;
  namespace "urn:srl_nokia/tools-vxlan-tunnel";
  prefix srl_nokia-tools-vxlan-tunnel;

  // import some basic types

  import srl_nokia-common {
    prefix srl_nokia-comm;
  }

  import srl_nokia-tools-tunnel { 
    prefix srl_nokia-tools-tunnel; 
  }

  description
    "Model for operational commands on vxlan tunnels.";

  revision 2020-12-31 {
    description
      "SRLinux 20.12.1";
  }

  grouping tools-vxlan-tunnel-vtep-top {
    description
      "Top-level grouping for vxlan-tunnel vtep tools.";
    list vtep {
      key "address";
      description
        "The IP address that identifies the remote VXLAN Termination Endpoint (VTEP).";
      leaf address {
        type srl_nokia-comm:ip-address;
        description
          "The IP address that identifies the remote VXLAN Termination Endpoint (VTEP).";
      }
      container statistics {
        leaf clear {
          type empty;
        }
      }
    }
  }

  grouping tools-vxlan-tunnel-top {
    description
      "Top-level grouping for vxlan-tunnel tools.";
    container vxlan-tunnel {
      container statistics {
        leaf clear {
          type empty;
        }
      }
      uses tools-vxlan-tunnel-vtep-top;
    }
  }

  augment "/srl_nokia-tools-tunnel:tunnel" {
    uses tools-vxlan-tunnel-top;
  }
}
