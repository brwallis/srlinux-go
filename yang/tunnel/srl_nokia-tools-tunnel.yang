module srl_nokia-tools-tunnel {
  yang-version 1.1;

  // namespace
  namespace "urn:srl_nokia/tools-tunnel";
  prefix "srl_nokia-tools-tunnel";

  import srl_nokia-common {
    prefix srl_nokia-comm;
  }
  import srl_nokia-features {
    prefix srl_nokia-feat;
  }
  import srl_nokia-extensions {
    prefix srl_nokia-ext;
  }

  revision 2020-10-31 {
    description
      "SRLinux 20.10.1";
  }

  // typedef statements

  // groupings 

  grouping tools-tunnel-top { 
    container tunnel {
      srl_nokia-ext:first-released "20.10.1";
      description
        "This model collects all config and state aspects of the tools-tunnel table
         in SRLinux.";
    }
  }
  uses tools-tunnel-top;
}
